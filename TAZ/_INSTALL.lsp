(defun taz_instalacja()
  (if (equal (vl-string-search ";C:\\TAZ\\GEN" (vla-get-SupportPath (vla-get-files  (vla-get-preferences (vlax-get-Acad-object))))) nil)
    (vla-put-SupportPath (vla-get-files  (vla-get-preferences (vlax-get-Acad-object))) (strcat (vla-get-SupportPath (vla-get-files  (vla-get-preferences (vlax-get-Acad-object)))) ";C:\\TAZ\\GEN"))
    (princ)
  )
  (if (equal (vl-string-search ";C:\\TAZ\\STL" (vla-get-SupportPath (vla-get-files  (vla-get-preferences (vlax-get-Acad-object))))) nil)
    (vla-put-SupportPath (vla-get-files  (vla-get-preferences (vlax-get-Acad-object))) (strcat (vla-get-SupportPath (vla-get-files  (vla-get-preferences (vlax-get-Acad-object)))) ";C:\\TAZ\\STL"))
    (princ)
  )
  (if (equal (vl-string-search ";C:\\TAZ\\IMG" (vla-get-SupportPath (vla-get-files  (vla-get-preferences (vlax-get-Acad-object))))) nil)
    (vla-put-SupportPath (vla-get-files  (vla-get-preferences (vlax-get-Acad-object))) (strcat (vla-get-SupportPath (vla-get-files  (vla-get-preferences (vlax-get-Acad-object)))) ";C:\\TAZ\\IMG"))
    (princ)
  )
  (if (equal (findfile (strcat (vla-get-PrinterStyleSheetPath (vla-get-files  (vla-get-preferences (vlax-get-Acad-object)))) "\\taz.ctb")) nil)
    (vl-file-copy "C:\\TAZ\\CTB\\taz.ctb" (strcat (vla-get-PrinterStyleSheetPath (vla-get-files  (vla-get-preferences (vlax-get-Acad-object)))) "\\taz.ctb"))
    (princ)
  )
)
(taz_instalacja)
(vla-load (vla-get-menugroups (vlax-get-acad-object)) "C:\\TAZ\\taz.cuix")
(command "-TOOLBAR" "TAZ" "Float" "20,230" "1")
(princ "\n########## ZAINSTALOWANO TOOLBAR AZ ##########")
(princ)
