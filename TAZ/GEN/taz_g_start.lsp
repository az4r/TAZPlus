(defun taz_wczytaj_warstwy()
  (setq taz_aktualna_warstwa (getvar "CLAYER"))
  (if (tblsearch "LAYER" "taz___thin")
    (princ)
    (command "_layer" "_M" "taz___thin" "_C" "1" "" "")
  )
  (if (tblsearch "LAYER" "taz___view")
    (princ)
    (command "_layer" "_M" "taz___view" "_C" "2" "" "")
  )
  (if (tblsearch "LAYER" "taz___section")
    (princ)
    (command "_layer" "_M" "taz___section" "_C" "3" "" "")
  )
  (if (tblsearch "LAYER" "taz___hidden")
    (princ)
    (progn
      (if (tblsearch "LTYPE" "HIDDEN")
        (princ)
        (command "_linetype" "_L" "HIDDEN" "gcadiso.lin" "")
      )
      (command "_layer" "_M" "taz___hidden" "_C" "4" "" "_L" "HIDDEN" "" "")
    )
  )
  (if (tblsearch "LAYER" "taz___help")
    (princ)
    (command "_layer" "_M" "taz___help" "_C" "6" "" "_P" "_N" "" "")
  )
  (if (tblsearch "LAYER" "taz___cut")
    (princ)
    (progn
      (if (tblsearch "LTYPE" "DASHED")
        (princ)
        (command "_linetype" "_L" "DASHED" "gcadiso.lin" "")
      )
      (command "_layer" "_M" "taz___cut" "_C" "1" "" "_L" "DASHED" "" "")
    )
  )
  (if (tblsearch "LAYER" "taz___axis")
    (princ)
    (progn
      (if (tblsearch "LTYPE" "CENTER")
        (princ)
        (command "_linetype" "_L" "CENTER" "gcadiso.lin" "")
      )
      (command "_layer" "_M" "taz___axis" "_C" "7" "" "_L" "CENTER" "" "")
    )
  )
  (if (tblsearch "LAYER" "taz___hatch")
    (princ)
    (command "_layer" "_M" "taz___hatch" "_C" "8" "" "")
  )
  (if (tblsearch "LAYER" "taz___text")
    (princ)
    (command "_layer" "_M" "taz___text" "_C" "1" "" "")
  )
  (command "_layer" "_S" taz_aktualna_warstwa "")
  (princ)
)

(defun taz_warstwa_zero()
  (command "_layer" "_S" "0" "")
  (princ)
)

(defun taz_warstwa_thin()
  (if (tblsearch "LAYER" "taz___thin")
    (command "_layer" "_S" "taz___thin" "")
    (progn
      (taz_wczytaj_warstwy)
      (command "_layer" "_S" "taz___thin" "")
    )
  )
  (princ)
)

(defun taz_warstwa_view()
  (if (tblsearch "LAYER" "taz___view")
    (command "_layer" "_S" "taz___view" "")
    (progn
      (taz_wczytaj_warstwy)
      (command "_layer" "_S" "taz___view" "")
    )
  )
  (princ)
)

(defun taz_warstwa_section()
  (if (tblsearch "LAYER" "taz___section")
    (command "_layer" "_S" "taz___section" "")
    (progn
      (taz_wczytaj_warstwy)
      (command "_layer" "_S" "taz___section" "")
    )
  )
  (princ)
)

(defun taz_warstwa_hidden()
  (if (tblsearch "LAYER" "taz___hidden")
    (command "_layer" "_S" "taz___hidden" "")
    (progn
      (taz_wczytaj_warstwy)
      (command "_layer" "_S" "taz___hidden" "")
    )
  )
  (princ)
)

(defun taz_warstwa_help()
  (if (tblsearch "LAYER" "taz___help")
    (command "_layer" "_S" "taz___help" "")
    (progn
      (taz_wczytaj_warstwy)
      (command "_layer" "_S" "taz___help" "")
    )
  )
  (princ)
)

(defun taz_warstwa_cut()
  (if (tblsearch "LAYER" "taz___cut")
    (command "_layer" "_S" "taz___cut" "")
    (progn
      (taz_wczytaj_warstwy)
      (command "_layer" "_S" "taz___cut" "")
    )
  )
  (princ)
)

(defun taz_warstwa_axis()
  (if (tblsearch "LAYER" "taz___axis")
    (command "_layer" "_S" "taz___axis" "")
    (progn
      (taz_wczytaj_warstwy)
      (command "_layer" "_S" "taz___axis" "")
    )
  )
  (princ)
)

(defun taz_warstwa_hatch()
  (if (tblsearch "LAYER" "taz___hatch")
    (command "_layer" "_S" "taz___hatch" "")
    (progn
      (taz_wczytaj_warstwy)
      (command "_layer" "_S" "taz___hatch" "")
    )
  )
  (princ)
)

(defun taz_wczytaj_style_tekstu()
  (setq taz_aktualny_styl_tekstu (getvar "TEXTSTYLE"))
  (if (tblsearch "STYLE" "taz_ts")
    (princ)
    (progn
      (command "-style" "taz_ts" "Arial" "0" "1" "0" "_N" "_N")
    )
  )
  (command "_setvar" "TEXTSTYLE" taz_aktualny_styl_tekstu)
  (princ)
)

(defun taz_wczytaj_style_wymiarow()
  (setq taz_aktualny_styl_wymiarow (getvar "DIMSTYLE"))
  (if (tblsearch "DIMSTYLE" "taz_ds_1")
    (princ)
    (progn
      (command "-dimstyle" "_AN" "_N" "taz_ds_1" "")
      (command "_setvar" "DIMDLE" "1.25")
      (command "_setvar" "DIMDLI" "0")
      (command "_setvar" "DIMEXE" "1.25")
      (command "_setvar" "DIMEXO" "2.5")
      (command "_setvar" "DIMFXL" "25")
      (command "_setvar" "DIMBLK" "Oblique")
      (command "_setvar" "DIMASZ" "2.5")
      (command "_setvar" "DIMCEN" "0")
      (command "_setvar" "DIMARCSYM" "1")
      (command "_setvar" "DIMTXSTY" "taz_ts")
      (command "_setvar" "DIMTXT" "2.5")
      (command "_setvar" "DIMTFAC" (/ (float 1) 30))
      (command "_setvar" "DIMTAD" "0")
      (command "_setvar" "DIMGAP" "0")
      (command "_setvar" "DIMTMOVE" "1")
      (command "_setvar" "DIMDEC" "1")
      (command "_setvar" "DIMDSEP" ".")
      (command "_setvar" "DIMRND" "1")
      (command "_setvar" "DIMZIN" "9")
      (command "_setvar" "DIMALTD" "2")
      (command "_setvar" "DIMALTF" "25.4")
      (command "_setvar" "DIMTOLJ" "1")
      (command "_setvar" "DIMTDEC" "1")
      (command "_setvar" "DIMTVP" "0.8")
      (command "_setvar" "DIMCLRD" "256")
      (command "_setvar" "DIMCLRE" "256")
      (command "_setvar" "DIMCLRT" "256")
      (command "_setvar" "DIMTFILLCLR" "256")
      (command "_setvar" "DIMSCALE" "1")
      (command "-dimstyle" "_S" "taz_ds_1" "_Y")
    )
  )
  (if (tblsearch "DIMSTYLE" "taz_ds_5")
    (princ)
    (progn
      (command "-dimstyle" "_AN" "_N" "taz_ds_5" "")
      (command "_setvar" "DIMDLE" "1.25")
      (command "_setvar" "DIMDLI" "0")
      (command "_setvar" "DIMEXE" "1.25")
      (command "_setvar" "DIMEXO" "2.5")
      (command "_setvar" "DIMFXL" "25")
      (command "_setvar" "DIMBLK" "Oblique")
      (command "_setvar" "DIMASZ" "2.5")
      (command "_setvar" "DIMCEN" "0")
      (command "_setvar" "DIMARCSYM" "1")
      (command "_setvar" "DIMTXSTY" "taz_ts")
      (command "_setvar" "DIMTXT" "2.5")
      (command "_setvar" "DIMTFAC" (/ (float 1) 30))
      (command "_setvar" "DIMTAD" "0")
      (command "_setvar" "DIMGAP" "0")
      (command "_setvar" "DIMTMOVE" "1")
      (command "_setvar" "DIMDEC" "1")
      (command "_setvar" "DIMDSEP" ".")
      (command "_setvar" "DIMRND" "1")
      (command "_setvar" "DIMZIN" "9")
      (command "_setvar" "DIMALTD" "2")
      (command "_setvar" "DIMALTF" "25.4")
      (command "_setvar" "DIMTOLJ" "1")
      (command "_setvar" "DIMTDEC" "1")
      (command "_setvar" "DIMTVP" "0.8")
      (command "_setvar" "DIMCLRD" "256")
      (command "_setvar" "DIMCLRE" "256")
      (command "_setvar" "DIMCLRT" "256")
      (command "_setvar" "DIMTFILLCLR" "256")
      (command "_setvar" "DIMSCALE" "5")
      (command "-dimstyle" "_S" "taz_ds_5" "_Y")
    )
  )
  (if (tblsearch "DIMSTYLE" "taz_ds_10")
    (princ)
    (progn
      (command "-dimstyle" "_AN" "_N" "taz_ds_10" "")
      (command "_setvar" "DIMDLE" "1.25")
      (command "_setvar" "DIMDLI" "0")
      (command "_setvar" "DIMEXE" "1.25")
      (command "_setvar" "DIMEXO" "2.5")
      (command "_setvar" "DIMFXL" "25")
      (command "_setvar" "DIMBLK" "Oblique")
      (command "_setvar" "DIMASZ" "2.5")
      (command "_setvar" "DIMCEN" "0")
      (command "_setvar" "DIMARCSYM" "1")
      (command "_setvar" "DIMTXSTY" "taz_ts")
      (command "_setvar" "DIMTXT" "2.5")
      (command "_setvar" "DIMTFAC" (/ (float 1) 30))
      (command "_setvar" "DIMTAD" "0")
      (command "_setvar" "DIMGAP" "0")
      (command "_setvar" "DIMTMOVE" "1")
      (command "_setvar" "DIMDEC" "1")
      (command "_setvar" "DIMDSEP" ".")
      (command "_setvar" "DIMRND" "1")
      (command "_setvar" "DIMZIN" "9")
      (command "_setvar" "DIMALTD" "2")
      (command "_setvar" "DIMALTF" "25.4")
      (command "_setvar" "DIMTOLJ" "1")
      (command "_setvar" "DIMTDEC" "1")
      (command "_setvar" "DIMTVP" "0.8")
      (command "_setvar" "DIMCLRD" "256")
      (command "_setvar" "DIMCLRE" "256")
      (command "_setvar" "DIMCLRT" "256")
      (command "_setvar" "DIMTFILLCLR" "256")
      (command "_setvar" "DIMSCALE" "10")
      (command "-dimstyle" "_S" "taz_ds_10" "_Y")
    )
  )
  (if (tblsearch "DIMSTYLE" "taz_ds_20")
    (princ)
    (progn
      (command "-dimstyle" "_AN" "_N" "taz_ds_20" "")
      (command "_setvar" "DIMDLE" "1.25")
      (command "_setvar" "DIMDLI" "0")
      (command "_setvar" "DIMEXE" "1.25")
      (command "_setvar" "DIMEXO" "2.5")
      (command "_setvar" "DIMFXL" "25")
      (command "_setvar" "DIMBLK" "Oblique")
      (command "_setvar" "DIMASZ" "2.5")
      (command "_setvar" "DIMCEN" "0")
      (command "_setvar" "DIMARCSYM" "1")
      (command "_setvar" "DIMTXSTY" "taz_ts")
      (command "_setvar" "DIMTXT" "2.5")
      (command "_setvar" "DIMTFAC" (/ (float 1) 30))
      (command "_setvar" "DIMTAD" "0")
      (command "_setvar" "DIMGAP" "0")
      (command "_setvar" "DIMTMOVE" "1")
      (command "_setvar" "DIMDEC" "1")
      (command "_setvar" "DIMDSEP" ".")
      (command "_setvar" "DIMRND" "1")
      (command "_setvar" "DIMZIN" "9")
      (command "_setvar" "DIMALTD" "2")
      (command "_setvar" "DIMALTF" "25.4")
      (command "_setvar" "DIMTOLJ" "1")
      (command "_setvar" "DIMTDEC" "1")
      (command "_setvar" "DIMTVP" "0.8")
      (command "_setvar" "DIMCLRD" "256")
      (command "_setvar" "DIMCLRE" "256")
      (command "_setvar" "DIMCLRT" "256")
      (command "_setvar" "DIMTFILLCLR" "256")
      (command "_setvar" "DIMSCALE" "20")
      (command "-dimstyle" "_S" "taz_ds_20" "_Y")
    )
  )
  (if (tblsearch "DIMSTYLE" "taz_ds_50")
    (princ)
    (progn
      (command "-dimstyle" "_AN" "_N" "taz_ds_50" "")
      (command "_setvar" "DIMDLE" "1.25")
      (command "_setvar" "DIMDLI" "0")
      (command "_setvar" "DIMEXE" "1.25")
      (command "_setvar" "DIMEXO" "2.5")
      (command "_setvar" "DIMFXL" "25")
      (command "_setvar" "DIMBLK" "Oblique")
      (command "_setvar" "DIMASZ" "2.5")
      (command "_setvar" "DIMCEN" "0")
      (command "_setvar" "DIMARCSYM" "1")
      (command "_setvar" "DIMTXSTY" "taz_ts")
      (command "_setvar" "DIMTXT" "2.5")
      (command "_setvar" "DIMTFAC" (/ (float 1) 30))
      (command "_setvar" "DIMTAD" "0")
      (command "_setvar" "DIMGAP" "0")
      (command "_setvar" "DIMTMOVE" "1")
      (command "_setvar" "DIMDEC" "1")
      (command "_setvar" "DIMDSEP" ".")
      (command "_setvar" "DIMRND" "1")
      (command "_setvar" "DIMZIN" "9")
      (command "_setvar" "DIMALTD" "2")
      (command "_setvar" "DIMALTF" "25.4")
      (command "_setvar" "DIMTOLJ" "1")
      (command "_setvar" "DIMTDEC" "1")
      (command "_setvar" "DIMTVP" "0.8")
      (command "_setvar" "DIMCLRD" "256")
      (command "_setvar" "DIMCLRE" "256")
      (command "_setvar" "DIMCLRT" "256")
      (command "_setvar" "DIMTFILLCLR" "256")
      (command "_setvar" "DIMSCALE" "50")
      (command "-dimstyle" "_S" "taz_ds_50" "_Y")
    )
  )
  (if (tblsearch "DIMSTYLE" "taz_ds_100")
    (princ)
    (progn
      (command "-dimstyle" "_AN" "_N" "taz_ds_100" "")
      (command "_setvar" "DIMDLE" "1.25")
      (command "_setvar" "DIMDLI" "0")
      (command "_setvar" "DIMEXE" "1.25")
      (command "_setvar" "DIMEXO" "2.5")
      (command "_setvar" "DIMFXL" "25")
      (command "_setvar" "DIMBLK" "Oblique")
      (command "_setvar" "DIMASZ" "2.5")
      (command "_setvar" "DIMCEN" "0")
      (command "_setvar" "DIMARCSYM" "1")
      (command "_setvar" "DIMTXSTY" "taz_ts")
      (command "_setvar" "DIMTXT" "2.5")
      (command "_setvar" "DIMTFAC" (/ (float 1) 30))
      (command "_setvar" "DIMTAD" "0")
      (command "_setvar" "DIMGAP" "0")
      (command "_setvar" "DIMTMOVE" "1")
      (command "_setvar" "DIMDEC" "1")
      (command "_setvar" "DIMDSEP" ".")
      (command "_setvar" "DIMRND" "1")
      (command "_setvar" "DIMZIN" "9")
      (command "_setvar" "DIMALTD" "2")
      (command "_setvar" "DIMALTF" "25.4")
      (command "_setvar" "DIMTOLJ" "1")
      (command "_setvar" "DIMTDEC" "1")
      (command "_setvar" "DIMTVP" "0.8")
      (command "_setvar" "DIMCLRD" "256")
      (command "_setvar" "DIMCLRE" "256")
      (command "_setvar" "DIMCLRT" "256")
      (command "_setvar" "DIMTFILLCLR" "256")
      (command "_setvar" "DIMSCALE" "100")
      (command "-dimstyle" "_S" "taz_ds_100" "_Y")
    )
  )
  (if (tblsearch "DIMSTYLE" "taz_ds_200")
    (princ)
    (progn
      (command "-dimstyle" "_AN" "_N" "taz_ds_200" "")
      (command "_setvar" "DIMDLE" "1.25")
      (command "_setvar" "DIMDLI" "0")
      (command "_setvar" "DIMEXE" "1.25")
      (command "_setvar" "DIMEXO" "2.5")
      (command "_setvar" "DIMFXL" "25")
      (command "_setvar" "DIMBLK" "Oblique")
      (command "_setvar" "DIMASZ" "2.5")
      (command "_setvar" "DIMCEN" "0")
      (command "_setvar" "DIMARCSYM" "1")
      (command "_setvar" "DIMTXSTY" "taz_ts")
      (command "_setvar" "DIMTXT" "2.5")
      (command "_setvar" "DIMTFAC" (/ (float 1) 30))
      (command "_setvar" "DIMTAD" "0")
      (command "_setvar" "DIMGAP" "0")
      (command "_setvar" "DIMTMOVE" "1")
      (command "_setvar" "DIMDEC" "1")
      (command "_setvar" "DIMDSEP" ".")
      (command "_setvar" "DIMRND" "1")
      (command "_setvar" "DIMZIN" "9")
      (command "_setvar" "DIMALTD" "2")
      (command "_setvar" "DIMALTF" "25.4")
      (command "_setvar" "DIMTOLJ" "1")
      (command "_setvar" "DIMTDEC" "1")
      (command "_setvar" "DIMTVP" "0.8")
      (command "_setvar" "DIMCLRD" "256")
      (command "_setvar" "DIMCLRE" "256")
      (command "_setvar" "DIMCLRT" "256")
      (command "_setvar" "DIMTFILLCLR" "256")
      (command "_setvar" "DIMSCALE" "200")
      (command "-dimstyle" "_S" "taz_ds_200" "_Y")
    )
  )
  (command "-dimstyle" "_R" taz_aktualny_styl_wymiarow)
  (princ)
)

(defun taz_wczytaj_style_wielolinii_odniesienia()
  (setq taz_aktualny_styl_wielolinii_odniesienia (getvar "CMLEADERSTYLE"))
  (if (dictsearch (cdr (assoc -1 (dictSearch (namedObjDict) "ACAD_MLEADERSTYLE"))) "taz_mls_1")
    (princ)
    (progn
      (setq taz_baza_styli_wielolinii_odniesienia (vlax-ename->vla-object (cdr (assoc -1 (dictSearch (namedObjDict) "ACAD_MLEADERSTYLE")))))
      (setq taz_vtaz_mls_1 (vlax-invoke-method taz_baza_styli_wielolinii_odniesienia 'AddObject "taz_mls_1" "AcDbMLeaderStyle"))
      (vlax-put-property taz_vtaz_mls_1 'ArrowSize 2.5)
      (vlax-put-property taz_vtaz_mls_1 'BreakSize 2.5)
      (vlax-put-property taz_vtaz_mls_1 'MaxLeaderSegmentsPoints 0)
      (vlax-put-property taz_vtaz_mls_1 'TextStyle "taz_ts")
      (vlax-put-property taz_vtaz_mls_1 'TextAngleType 1)
      (vlax-put-property taz_vtaz_mls_1 'TextHeight 2.5)
      (vlax-put-property taz_vtaz_mls_1 'TextLeftAttachmentType 3)
      (vlax-put-property taz_vtaz_mls_1 'LandingGap 0.625)
      (vlax-put-property taz_vtaz_mls_1 'ScaleFactor 1)
    )
  )
  (if (dictsearch (cdr (assoc -1 (dictSearch (namedObjDict) "ACAD_MLEADERSTYLE"))) "taz_mls_5")
    (princ)
    (progn
      (setq taz_baza_styli_wielolinii_odniesienia (vlax-ename->vla-object (cdr (assoc -1 (dictSearch (namedObjDict) "ACAD_MLEADERSTYLE")))))
      (setq taz_vtaz_mls_5 (vlax-invoke-method taz_baza_styli_wielolinii_odniesienia 'AddObject "taz_mls_5" "AcDbMLeaderStyle"))
      (vlax-put-property taz_vtaz_mls_5 'ArrowSize 2.5)
      (vlax-put-property taz_vtaz_mls_5 'BreakSize 2.5)
      (vlax-put-property taz_vtaz_mls_5 'MaxLeaderSegmentsPoints 0)
      (vlax-put-property taz_vtaz_mls_5 'TextStyle "taz_ts")
      (vlax-put-property taz_vtaz_mls_5 'TextAngleType 1)
      (vlax-put-property taz_vtaz_mls_5 'TextHeight 2.5)
      (vlax-put-property taz_vtaz_mls_5 'TextLeftAttachmentType 3)
      (vlax-put-property taz_vtaz_mls_5 'LandingGap 0.625)
      (vlax-put-property taz_vtaz_mls_5 'ScaleFactor 5)
    )
  )
  (if (dictsearch (cdr (assoc -1 (dictSearch (namedObjDict) "ACAD_MLEADERSTYLE"))) "taz_mls_10")
    (princ)
    (progn
      (setq taz_baza_styli_wielolinii_odniesienia (vlax-ename->vla-object (cdr (assoc -1 (dictSearch (namedObjDict) "ACAD_MLEADERSTYLE")))))
      (setq taz_vtaz_mls_10 (vlax-invoke-method taz_baza_styli_wielolinii_odniesienia 'AddObject "taz_mls_10" "AcDbMLeaderStyle"))
      (vlax-put-property taz_vtaz_mls_10 'ArrowSize 2.5)
      (vlax-put-property taz_vtaz_mls_10 'BreakSize 2.5)
      (vlax-put-property taz_vtaz_mls_10 'MaxLeaderSegmentsPoints 0)
      (vlax-put-property taz_vtaz_mls_10 'TextStyle "taz_ts")
      (vlax-put-property taz_vtaz_mls_10 'TextAngleType 1)
      (vlax-put-property taz_vtaz_mls_10 'TextHeight 2.5)
      (vlax-put-property taz_vtaz_mls_10 'TextLeftAttachmentType 3)
      (vlax-put-property taz_vtaz_mls_10 'LandingGap 0.625)
      (vlax-put-property taz_vtaz_mls_10 'ScaleFactor 10)
    )
  )
  (if (dictsearch (cdr (assoc -1 (dictSearch (namedObjDict) "ACAD_MLEADERSTYLE"))) "taz_mls_20")
    (princ)
    (progn
      (setq taz_baza_styli_wielolinii_odniesienia (vlax-ename->vla-object (cdr (assoc -1 (dictSearch (namedObjDict) "ACAD_MLEADERSTYLE")))))
      (setq taz_vtaz_mls_20 (vlax-invoke-method taz_baza_styli_wielolinii_odniesienia 'AddObject "taz_mls_20" "AcDbMLeaderStyle"))
      (vlax-put-property taz_vtaz_mls_20 'ArrowSize 2.5)
      (vlax-put-property taz_vtaz_mls_20 'BreakSize 2.5)
      (vlax-put-property taz_vtaz_mls_20 'MaxLeaderSegmentsPoints 0)
      (vlax-put-property taz_vtaz_mls_20 'TextStyle "taz_ts")
      (vlax-put-property taz_vtaz_mls_20 'TextAngleType 1)
      (vlax-put-property taz_vtaz_mls_20 'TextHeight 2.5)
      (vlax-put-property taz_vtaz_mls_20 'TextLeftAttachmentType 3)
      (vlax-put-property taz_vtaz_mls_20 'LandingGap 0.625)
      (vlax-put-property taz_vtaz_mls_20 'ScaleFactor 20)
    )
  )
  (if (dictsearch (cdr (assoc -1 (dictSearch (namedObjDict) "ACAD_MLEADERSTYLE"))) "taz_mls_50")
    (princ)
    (progn
      (setq taz_baza_styli_wielolinii_odniesienia (vlax-ename->vla-object (cdr (assoc -1 (dictSearch (namedObjDict) "ACAD_MLEADERSTYLE")))))
      (setq taz_vtaz_mls_50 (vlax-invoke-method taz_baza_styli_wielolinii_odniesienia 'AddObject "taz_mls_50" "AcDbMLeaderStyle"))
      (vlax-put-property taz_vtaz_mls_50 'ArrowSize 2.5)
      (vlax-put-property taz_vtaz_mls_50 'BreakSize 2.5)
      (vlax-put-property taz_vtaz_mls_50 'MaxLeaderSegmentsPoints 0)
      (vlax-put-property taz_vtaz_mls_50 'TextStyle "taz_ts")
      (vlax-put-property taz_vtaz_mls_50 'TextAngleType 1)
      (vlax-put-property taz_vtaz_mls_50 'TextHeight 2.5)
      (vlax-put-property taz_vtaz_mls_50 'TextLeftAttachmentType 3)
      (vlax-put-property taz_vtaz_mls_50 'LandingGap 0.625)
      (vlax-put-property taz_vtaz_mls_50 'ScaleFactor 50)
    )
  )
  (if (dictsearch (cdr (assoc -1 (dictSearch (namedObjDict) "ACAD_MLEADERSTYLE"))) "taz_mls_100")
    (princ)
    (progn
      (setq taz_baza_styli_wielolinii_odniesienia (vlax-ename->vla-object (cdr (assoc -1 (dictSearch (namedObjDict) "ACAD_MLEADERSTYLE")))))
      (setq taz_vtaz_mls_100 (vlax-invoke-method taz_baza_styli_wielolinii_odniesienia 'AddObject "taz_mls_100" "AcDbMLeaderStyle"))
      (vlax-put-property taz_vtaz_mls_100 'ArrowSize 2.5)
      (vlax-put-property taz_vtaz_mls_100 'BreakSize 2.5)
      (vlax-put-property taz_vtaz_mls_100 'MaxLeaderSegmentsPoints 0)
      (vlax-put-property taz_vtaz_mls_100 'TextStyle "taz_ts")
      (vlax-put-property taz_vtaz_mls_100 'TextAngleType 1)
      (vlax-put-property taz_vtaz_mls_100 'TextHeight 2.5)
      (vlax-put-property taz_vtaz_mls_100 'TextLeftAttachmentType 3)
      (vlax-put-property taz_vtaz_mls_100 'LandingGap 0.625)
      (vlax-put-property taz_vtaz_mls_100 'ScaleFactor 100)
    )
  )
  (if (dictsearch (cdr (assoc -1 (dictSearch (namedObjDict) "ACAD_MLEADERSTYLE"))) "taz_mls_200")
    (princ)
    (progn
      (setq taz_baza_styli_wielolinii_odniesienia (vlax-ename->vla-object (cdr (assoc -1 (dictSearch (namedObjDict) "ACAD_MLEADERSTYLE")))))
      (setq taz_vtaz_mls_200 (vlax-invoke-method taz_baza_styli_wielolinii_odniesienia 'AddObject "taz_mls_200" "AcDbMLeaderStyle"))
      (vlax-put-property taz_vtaz_mls_200 'ArrowSize 2.5)
      (vlax-put-property taz_vtaz_mls_200 'BreakSize 2.5)
      (vlax-put-property taz_vtaz_mls_200 'MaxLeaderSegmentsPoints 0)
      (vlax-put-property taz_vtaz_mls_200 'TextStyle "taz_ts")
      (vlax-put-property taz_vtaz_mls_200 'TextAngleType 1)
      (vlax-put-property taz_vtaz_mls_200 'TextHeight 2.5)
      (vlax-put-property taz_vtaz_mls_200 'TextLeftAttachmentType 3)
      (vlax-put-property taz_vtaz_mls_200 'LandingGap 0.625)
      (vlax-put-property taz_vtaz_mls_200 'ScaleFactor 200)
    )
  )
  (command "_setvar" "CMLEADERSTYLE" taz_aktualny_styl_wielolinii_odniesienia)
)

(defun taz_skala_1()
  (command "_setvar" "TEXTSTYLE" "taz_ts")
  (command "_textsize" "2.5")
  (command "-dimstyle" "_R" "taz_ds_1")
  (command "_setvar" "CMLEADERSTYLE" "taz_mls_1")
  (setq taz_wspolczynnik_skali 1)
  (princ)
)

(defun taz_skala_5()
  (command "_setvar" "TEXTSTYLE" "taz_ts")
  (command "_textsize" "12.5")
  (command "-dimstyle" "_R" "taz_ds_5")
  (command "_setvar" "CMLEADERSTYLE" "taz_mls_5")
  (setq taz_wspolczynnik_skali 5)
  (princ)
)

(defun taz_skala_10()
  (command "_setvar" "TEXTSTYLE" "taz_ts")
  (command "_textsize" "25")
  (command "-dimstyle" "_R" "taz_ds_10")
  (command "_setvar" "CMLEADERSTYLE" "taz_mls_10")
  (setq taz_wspolczynnik_skali 10)
  (princ)
)

(defun taz_skala_20()
  (command "_setvar" "TEXTSTYLE" "taz_ts")
  (command "_textsize" "50")
  (command "-dimstyle" "_R" "taz_ds_20")
  (command "_setvar" "CMLEADERSTYLE" "taz_mls_20")
  (setq taz_wspolczynnik_skali 20)
  (princ)
)

(defun taz_skala_50()
  (command "_setvar" "TEXTSTYLE" "taz_ts")
  (command "_textsize" "125")
  (command "-dimstyle" "_R" "taz_ds_50")
  (command "_setvar" "CMLEADERSTYLE" "taz_mls_50")
  (setq taz_wspolczynnik_skali 50)
  (princ)
)

(defun taz_skala_100()
  (command "_setvar" "TEXTSTYLE" "taz_ts")
  (command "_textsize" "250")
  (command "-dimstyle" "_R" "taz_ds_100")
  (command "_setvar" "CMLEADERSTYLE" "taz_mls_100")
  (setq taz_wspolczynnik_skali 100)
  (princ)
)

(defun taz_skala_200()
  (command "_setvar" "TEXTSTYLE" "taz_ts")
  (command "_textsize" "500")
  (command "-dimstyle" "_R" "taz_ds_200")
  (command "_setvar" "CMLEADERSTYLE" "taz_mls_200")
  (setq taz_wspolczynnik_skali 200)
  (princ)
)

(taz_wczytaj_warstwy)
(taz_wczytaj_style_tekstu)
(taz_wczytaj_style_wymiarow)
(taz_wczytaj_style_wielolinii_odniesienia)
(princ)
